module orchestration
{
	namespace "http://cablelabs.com/yang/nfv/orchestration";
	prefix cablelabs;


	organization "CableLabs";

	description
	"This module contains data types and rpc definitions for the nfv orchestration layer sample for the EPL use case";



	typedef epl_service_type
	{
		type enumeration {
			enum epl;
			enum ep-tree;
			enum ep-lan;
			enum evpl;
			enum evp-lan; 
			emum evp-tree;
		}
		reference "?";
		description
		"This enumeration contains the all EPL service types epl, evpl, .";
	}

	typedef up-down-state-type {
		type enumeration {
			enum up;
			enum down;
		}
		description
		"Type for specifying state of a circuit.";
	}

	typedef float {
		type binary {
			length "0..4";
		}
		description
		"32-bit IEEE floating point number" ;
	}


// XXX – some ideas that may not be necessary
	typedef interface-speed-type {
		type enumeration {
			enum "ten" {
				value 10;
			}
			enum "hundred" {
				value 100;
			}
			enum "thousand" {
				value 1000;
			}
		}
	}

	typedef interfaced-duplex-type {
		type enumeration {
			enum "half";
			enum "full";
		}
	}

	grouping common-packets-counters-type {
		leaf bytes {
			type yang:counter64;
		}
		leaf packets {
			type yang:counter64;
		}
		leaf errors {
			type yang:counter32;
		}
		leaf dropped {
			type yang:counter32;
		}
	}

	// XXX  - This from mef.
	typedef mep-id-type {
		type uint16 {
			range "1..8191";
		}
		description
		"Maintenance association End Point Identifier (MEPID): A small integer,
		unique over a given Maintenance Association, identifying a
		specific MEP.";
		reference "[802.1q] 3.19 and 19.2.1";
	}


	// XXX – need to look at instance id
	typedef circuit-reference {
		type string;
		description
		"Type to specify the connection between two endpoint NID's or circuit.";
		reference "[RFC3046]";
	}

	grouping circuit-metrics-grouping
	{

		leaf latency
		{
			type uint32 {
				range 0..65535;
			}
			description
			"Circuit latency allowed in microseconds.";

		}
		leaf throughput
		{
			leaf bps {
				type yang:counter64;
			}
			leaf pps {
				type yang:counter64;
			}
			description "Circuit throughput.";

		}
	}

	grouping circuit-attribute-group {
		leaf name
		{
			type string {
				length "0..64";
			}
		}
		container performance-sla
		{

			uses circuit-metrics-grouping;
			description
			"Performance SLA.";

		}
		leaf service-type
		{
			type epl-service-type;
			mandatory true;
		        default "epl";
			description
			"The service type for the EPL.";

		}

		leaf service-label
		{
			type string {
				length "0..32";
			}

			description
			"The label is dependent on the encapsulation type.
			For example if the encapsulation type was VLAN then label would be
			a VLAN tag.  If the encapsulation type is MPLS then the label would be e.g. RED or ORANGE";

		}

	}

	grouping circuit-grouping
	{
		container circuit-attribute-group
		{
			uses circuit-attributes;
		}
		container nids-managed {
			list nids-managed {
				key "nid-id";
				unique " nid-id ";
				description
				"The list of all NIDs hosting the circuit instance.
				Here the endpoint are the fist and last members in the list";
				uses nid-grouping;
			}
		}

	}


	grouping nid-grouping
	{
		description
		"An endpoint device is an Internet-capable computer hardware device on a TCP/IP network and
		for our purposes represents device that can be or emulate the functions as network devices
		that acts as a switch.";

		leaf enabled {
			type boolean;
			mandatory true;
			default false;
			description
			"Specifies if the NID is enabled.";
		}

		leaf nid-id {
			type inet:ip-address;
			mandatory true;
			description
			"An identifier that identifies a NID.
			The management IP address of the NID.";
		}
		//XXX – may not be needed
		leaf mac-address {
			type yang:mac-address;
			description
			"The MAC address of the NID.";
		}

		leaf nid-state
		{
			type up-down-state-type;
			mandatory true;
			default down;
			description
			"The NID up or down”;

		}


		container circuits-managed
		{
			list circuits-managed {
				key "circuit-reference";
				unique "circuit-reference";
				uses circuit-grouping;
				description
				"The list of all circuits managed by NID instance.";
			}
		}
	}


			// XXX create NID
		rpc orchestration_nfv_create {
			description
			"Create a NID endpoints with a switch or controller?";
			reference "";

			input {
				leaf nid-input
				{
					uses nid-grouping; //attributes
				}

			}
			output {
				leaf status
				{
					type uint32;
				}
				leaf nid-id
				{
					type nid-id;
				}
			}
		}

			// XXX create NID
		rpc orchestration_nfv_get {
			description
			"Create a NID endpoints with a switch or controller?
				Can not delete a NID with circuits";

			reference "";

			input {
				leaf nid-id
				{
					type nid-id;
				}

			}
			output {
				leaf status
				{
				type uint32;
				}
				leaf nid-output
				{
				uses nid-grouping; //attributes
				}

			}
		}


		// XXX create NID
		rpc orchestration_nfv_update {
			description
			"Create a NID endpoints with a switch or controller?
				Can not delete a NID with circuits";

			reference "";

			input {
				leaf nid-id
				{
					type nid-id;
				}
				leaf nid-input
				{
					uses nid-grouping; //attributes
				}


			}
			output {
				leaf status
				{
					type uint32;
				}
			 }
		}

		// XXX create NID
		rpc orchestration_nfv_delete {
			description
			"Create a NID endpoints with a switch or controller?
     			 Can not delete a NID with circuits";

			reference "";

			input {
				leaf nid-input
				{
					uses nid-grouping; //attributes
				}

			}
			output {
				leaf status
				{
					type uint32;
				}
				leaf nid-id
				{
					type nid-id;
				}
			}
		}

		rpc orchestration_circuit_create{
			description
			"Create a circuit on a part of NID endpoints and return a circuit id";
			reference "";

			input {
				leaf circuit-input
				{
					uses circuit-attributes;
				}
			}
			output {
				leaf status
				{
					type uint32;
				}
				leaf circuit-id
				{
					type circuit-reference;
				}
			}
		}

		rpc orchestration_circuit_get{
			description
			"Read and return a circuit definition given a circuit id";
			reference "";

			input {
				leaf circuit-id
				{
					type circuit-reference;
				}

			}
			output {
				leaf status
				{
					type uint32;
				}
				leaf circuit-output
				{
					uses circuit-attributes;
				}
			}
		}

		rpc orchestration_circuit_update{
			description
			"Update the attributes of an existing circuit given a circuit id.
			Changing the end point addresses constitutes a delete and create.
			Performance, encapsulation, and other attributes are primary attributes
			of interest";
			reference "";

			input {
				leaf circuit-id
				{
					type circuit-reference;
				}
				leaf circuit-input
				{
					uses circuit-attributes;
				}
			}
			output {
				leaf status
				{
					type uint32;
				}

			}
		}


		rpc orchestration_circuit_delete{
			description
			"Delete a given circuit id.";
			reference "";

			input {
				leaf circuit-id
				{
					type circuit-reference;
				}

			}
			output {
				leaf status
				{
					type uint32;
				}
			}
		}

		rpc orchestration_circuit_request_authorization{
			description
			" Send a request to a policy server to check authorization to perform circuit
			action.  ";
			reference "";

			input {
				leaf circuit-id
				{
					type circuit-reference;
				}
				leaf circuit-input
				{
					uses circuit-attributes;
				}
			}
			output {
				leaf status
				{
					type uint32;
				}
			}
		}

		rpc orchestration_circuit_performance_metrics {
			description
			" Given a circuitID retrieve the current performance metrics.";
			reference "";

			input {
				leaf circuit-id
				{
					type circuit-reference;
				}
			}
			output {
				leaf status
				{
					type uint32;
				}

			}
		}

		// XXX – notification or rpc?
		notification orchestration_circuit_fault_report {
			description
			" Given a circuitID resolve the current fault situation for the circuit.
			type of fault might be link down or performance ";
			reference "";

			input {
				uses circuit-input;
			}
			output {
				uses circuit-output;
			}
		}
}
